module ols {
    yang-version 1;
    namespace "urn:PajaritoTech:params:xml:ns:yang:ols";
    prefix "ols";

    import ietf-yang-types { prefix yang; }
    /* We avoid using common defs for lat/long as this explodes our REST API when autogenerated wiht yangtools
    import ietf-geo-location { prefix geo; }
    */

    organization "Pajarito Technologies LLC";
    contact "Frank Sandoval frank@pajaritotech.com";
    description "Defines Data Model of Optimal Load Shape module.

        This model supports the Optimal Load Shape framework defined by the SCTE. An OLS signal
        may be generated and made available by an electrical service provider daily, to allow electrical load
        generators to time their consumption to match the provider's optimal load shape. E.g. an electrical
        vehicle charger may spread load throughout the night to attenuate an evening peak.

        For geo-location definition see https://tools.ietf.org/id/draft-ietf-netmod-geo-location-02.xml#rfc.section.A

        Copyright (C) Pajarito Technologies LLC
        ";

    revision "2020-12-26" {
        description "Initial version";
    }

    /*
     * Typedefs
     */

     typedef optimal-load-value {
       description
         "Decimal degree (DD) used to express an optimal load at a given time.";
       type decimal64 {
         fraction-digits 3;
         range "-1.000..1.000";
       }
     }

     typedef degrees {
       type decimal64 {
         fraction-digits 16;
       }
       units "decimal degrees";
       description "Coordinate value.";
     }

     grouping geolocation-group {
        description
          "Our local subset of IETF geo-location";
          leaf latitude {
            type degrees;
            description
              "The latitude value on the astronomical body. The
               definition and precision of this measurement is
               indicated by the reference-frame value.";
          }
          leaf longitude {
            type degrees;
            description
              "The longitude value on the astronomical body. The
               definition and precision of this measurement is
               indicated by the reference-frame.";
          }
     }


     grouping optimal-load-group {
        description
            "a list of timestamped OLS values";
        list optimal-load {
          key "timestamp";
          leaf timestamp {
              type yang:date-and-time;
          }
          leaf ols-value {
              type optimal-load-value;
          }
        }
     }

    container ols {
      list ols-signal {
          config false;
          key "providerID";
          leaf providerID {
            type yang:uuid;
            description "a globally unique ID for the provider of this OLS signal";
          }
          uses geolocation-group;
          uses optimal-load-group;
          description "an Optimal Load Shape signal";
      }
    }
}
